module pnp-manager {

  namespace "http://example.com/pnp-manager";
  prefix pnp-manager;

  description
    "Customer facing services and actions for Pnp System Management";

  revision 2019-07-10 {
    description
      "Initial revision.";
  }

  container pnp-manager {
    description "Pnp System Management";

  }
}
