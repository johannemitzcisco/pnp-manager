module pnp-device {
  namespace "http://com/example/pnp-device";
  prefix pnp-device;

  import ietf-inet-types { prefix inet; }
  import tailf-ncs { prefix ncs; }
  import device { prefix device; }

  grouping pnp-grouping {
    leaf authgroup {
      type leafref {
        path "/ncs:devices/ncs:authgroups/ncs:group/ncs:name";
      }
    }
    leaf username {
      type string;
    }
    leaf password {
      type string;
    }
    leaf port {
      default "22";
      type inet:port-number;
    }
    leaf day0-file {
      type string;
    }
    list cfg-file-variable {
      key name;
      leaf name {
        type string;
      }
      leaf value {
        type string;
      }
    }
  }

  grouping pnp-device-grouping {
    uses device:device-grouping;

    leaf pnp-id {
      description "Device's unique id (eg. Serial Number)";
      type string;
    }
    //uses pnp-device:pnp-grouping;
  }

  augment /device:device-role {
    container pnp {
      description "Optional settings if this role is PnP related";  
      uses pnp-device:pnp-grouping;
    }
  }

  list pnp-device {
    description "PnP Device Configuration Service";

    key name;
    uses pnp-device:pnp-device-grouping {
      refine name {
        description "PnP Device Name";
      }
    }

    uses ncs:service-data;
    ncs:servicepoint pnp-device-servicepoint;
  }

}
